module yang-compiler {
  prefix yc;

  include yang-v1-extensions;

  organization
    "ClearPath Networks NFV R&D Group";

  contact
    "Web:  <http://www.clearpathnet.com>
     Code: <http://github.com/stormstack/yang-compiler>

     Author: Peter K. Lee <mailto:plee@clearpathnet.com>";

  description
    "This module provides YANG v1 language based schema compilations.";

  revision 2015-05-04 {
    description "Initial revision";
    reference "RFC-6020";
  }
    
  grouping compiler-rules {
    description
      "The compiler-rules specify parameters used during compile operation.";
    
    list map {
      description
        "The map defines a list of modules and their source description.  It is
         referenced by the compiler to locate the module for retrieval
         during include/import operation.";
      
      key name;
      leaf name { type string; }
      leaf source { type string; }
    }

    list extensions {
      leaf name     { type string; mandatory true; }
      leaf resolver { type binary; mandatory true; }
    }
    
    list importers {
      leaf regexp { type regexp; }
      leaf importer { type binary; }
      ordered-by user;
    }

    list procedures {
      leaf name { type string; mandatory true; }
      leaf exec { type binary; mandatory true; }
    }
  }

  grouping meta-module {
    description
      "The meta-module describes configuration structure for import/export operations.";
    
    leaf name   { type string; mandatory true; }
    leaf source { type uri; }
    leaf schema { type string; }
    
    uses compiler-rules;
  }

  uses compiler-rules;
  
  rpc import {
    input { uses meta-module; }
    output {
      leaf message { type string; }
    }
  }
  rpc export {
    input {
      leaf name { type string; mandatory true; }
      leaf format { type string; default json; }
    }
    output { uses meta-module; }
  }
}
