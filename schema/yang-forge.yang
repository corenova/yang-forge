module yang-forge {
  namespace "urn:corenova:yang:yang-forge";
  prefix forge;
  yang-version 1.1;

  import ietf-yang-types      { prefix yang; }
  import yang-meta-types      { prefix meta; }
  import node-package-manager { prefix npm; }

  organization
    "Corenova Technologies, Inc.";
  contact
    "Peter K. Lee <peter@corenova.com>";
  description
    "This module provides YANG schema and package management operations";

  revision 2016-11-09 {
    description "Updated to YANG 1.1 and revised with npm and commander module dependencies";
  }
  revision 2016-03-25 {
    description "Enhanced with 0.12.x functionality";
  }
  revision 2015-09-23 {
    description "Enhanced with 0.10.x functionality";
  }
  revision 2015-05-04 {
    description "Initial revision";
  }

  typedef core-identifier {
    type npm:package-name;
  }
  
  /*
   * Groupings
   */
  grouping core-essence {
    description
      "The core essence of a software module.";
    leaf id {
      type yang:uuid;
    }
    list module {
      key "tag";
      leaf tag {
        type yang:yang-identifier;
      }
    }
    container exports;
  }
  /*
   * Augment external configuration data nodes
   */
  augment "/npm:registry/package" {
    container core {
      uses forge:core-essence;
    }
    action build {
      description
        "Generate a core for this package entry and returns the primary module's schema";
      input {
        leaf force {
          type boolean;
          default false;
        }
      }
      output {
        
      }
    }
  }
  
  /*
   * Operational state data nodes
   */
  container store {
    config false;
    list core {
      key 'id';
      uses forge:core-essence;
    }
  }
  
  /*
   * Remote procedure operations
   */
  rpc import {
    description
      "Imports matching NPM package(s) into the local registry and returns the generated core(s)";
    input {
      uses npm:package-selection-choice;
    }
    output {
      leaf-list cores {
        type string;
      }
    }
  }
  rpc create {
    output {
      container core {
        uses forge:core-essence;
      }
    }
  }
}
