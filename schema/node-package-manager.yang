module node-package-manager {
  namespace "urn:corenova:yang:node-package-manager";
  prefix npm;
  yang-version 1.1;

  import yang-meta-types { prefix meta; }
  import file-system { prefix fs; }
  import node-js-types { prefix node; }
  include node-package-specification;
  
  organization
    "Corenova Technologies, Inc.";
  contact
    "Peter K. Lee <peter@corenova.com>";
  description
    "This module provides model-driven abstractions for Node.js Package Manager";
  revision 2016-11-08 {
    description
      "Initial revision.";
  }
  /*
   * Features
   */
  feature remote-registry {
    description "System provides remote registry transaction capability.";
  }
  /*
   * Groupings
   */
  grouping project {
    leaf name {
      type npm:package-name;
    }
    leaf description {
      type meta:description;
    }
    leaf created-on {
      config false;
      type yang:date-and-time;
    }
    leaf modified-on {
      config false;
      type yang:date-and-time;
    }
    leaf latest {
      config false;
      type leafref {
        path "../release/version";
      }
    }
    list release {
      key "version";
      leaf version {
        type meta:semantic-version;
      }
      leaf timestamp {
        type yang:date-and-time;
      }
      leaf stable {
        config false;
        type boolean;
      }
      leaf manifest {
        config false;
        type instance-identifier;
      }
    }
    leaf releases-count {
      config false;
      type uint16;
      default 0;
    }
    container downloads {
      config false;
      leaf last-day {
        type uint64;
        default 0;
      }
      leaf last-week {
        type uint64;
        default 0;
      }
      leaf last-month {
        type uint64;
        default 0;
      }
      leaf total {
        type uint64;
        default 0;
      }
    }
  }
  grouping projects-list {
    list project {
      key 'name';
      uses npm:project;
      action update;
    }
  }
  grouping packages-list {
    list package {
      key "name version";
      uses npm:package-manifest {
        augment "dependencies" {
          leaf-list missing {
            when "../scanned = true()";
            type npm:package-name;
          }
        }
        augment "dependencies/required" {
          when "../scanned = true()";
          leaf used {
            type boolean;
            default false;
          }
        }
      }
      leaf published-on {
        type yang:date-and-time;
      }
      leaf source {
        type instance-identifier;
        // must "starts-with(value(),'/npm:registry/source')"
      }
      leaf scanned {
        type boolean;
        default false;
      }
      action scan {
        input {
          leaf force {
            type boolean;
            default false;
          }
          leaf sync {
            type boolean;
            default false;
          }
        }
        output {
          leaf valid {
            type boolean;
            default false;
          }
          list dependency {
            key "name version";
            leaf name {
              type npm:package-name;
            }
            leaf version {
              type meta:semantic-version;
            }
            leaf-list dependents {
              type npm:package-name;
            }
          }
        }
      }
      action extract {
        input {
          leaf dest {
            type meta:file-name;
            mandatory true;
          }
          leaf dependencies {
            type boolean;
            default true;
          }
        }
        output {
          grouping extracted-module {
            leaf name {
              type npm:package-name;
              mandatory true;
            }
            leaf version {
              type meta:semantic-version;
              mandatory true;
            }
            leaf-list files {
              type meta:file-name;
            }
          }
          grouping dependency-modules-list {
            list module {
              key "name version";
              uses extracted-module;
              uses dependency-modules-list {
                when "../name";
              }
            }
          }
          uses extracted-module;
          uses dependency-modules-list;
        }
      }
      action serialize {
        description
          "Serializes current package manifest object into string format based on
           requested output format.";
        input {
          leaf format {
            type enumeration {
              enum json;
              enum yaml;
            }
            default json;
          }
        }
        output {
          leaf data {
            description "contains the serialized package manifest data";
            type string;
          }
        }
      }
    }
  }
  grouping source-archive {
    uses fs:archive {
      augment "file" {
        leaf scanned {
          type boolean;
          default false;
        }
        leaf-list imports {
          type npm:package-name;
        }
        leaf-list includes {
          type leafref {
            path "../../../../file/name";
          }
        }
        action scan {
          //when "(../format = 'js') or (../format = 'node')";
          input {
            leaf tag {
              type boolean;
              default false;
            }
          }
          output {
            leaf valid {
              type boolean;
              default false;
            }
          }
        }
      }
    }
    action resolve {
      description
        "attempts to resolve 'input' name and return a matching 'file' entry";
    }
  }
  grouping sources-list {
    list source {
      key "name";
      uses npm:source-archive;
    }
  }
  grouping package-selection-choice {
    grouping package-selection {
      leaf name {
        type npm:package-name;
        mandatory true;
      }
      leaf match {
        type union {
          type meta:semantic-version-match;
          type string {
            pattern "^latest$";
          }
        }
        default "latest";
      }
    }
    choice select {
      case single {
        uses package-selection;
      }
      case multiple {
        list package {
          key "name match";
          uses package-selection;
          min-elements 1;
          max-elements 50;
        }
      }
      mandatory true;
    }
    leaf filter {
      type enumeration {
        enum earliest;
        enum latest;
        enum all;
      }
      default all;
    }
  }
  /*
   * Configuration data nodes
   */
  container specification {
    leaf-list keywords {
      type meta:meta-identifier;
    }
  }
  container registry {
    config false;
    uses npm:projects-list;
    uses npm:packages-list {
    }
    uses npm:sources-list;
    leaf projects-count {
      type uint32;
      default 0;
    }
    leaf packages-count {
      type uint32;
      default 0;
    }
    leaf sources-count {
      type uint32;
      default 0;
    }
    action sync {
      if-feature npm:remote-registry;
      description
        "Synchronize with NPM registry for information about package(s)";
      input {
        uses npm:package-selection-choice;
        leaf host {
          type inet:uri;
          default "registry.npmjs.org";
        }
        leaf force {
          type boolean;
          default false;
        }
        leaf recursive {
          type boolean;
          default false;
        }
      }
      output {
        leaf packages {
          type uint32;
          default 0;
        }
        leaf sources {
          type uint32;
          default 0;
        }
      }
    }
    action query {
      description
        "Query local registry for matching package(s)";
      input {
        uses npm:package-selection-choice;
        leaf sync {
          description
            "When enabled, will perform sync with remote NPM registry";
          type boolean;
          default false;
        }
      }
      output {
        list package {
          key "name version";
          leaf name {
            type npm:package-name;
          }
          leaf version {
            type meta:semantic-version;
          }
        }
      }
    }
  }
  container policy {
    container cache {
      leaf enabled {
        type boolean;
        default true;
      }
      leaf directory {
        type meta:file-name;
        default "/tmp/npm-cache";
      }
    }
  }
  /*
   * Notifications
   */
  notification npm-registry-change {
    description
      "Generated when the set of packages in the internal registry has
       changed.";
  }
  /*
   * Remote Procedure Operations
   */
  rpc parse {
    description
      "Parses input JSON or JS object source into npm:package-manifest data model.";
    input {
      anydata source {
        description "JSON text or JS object representing package.json content";
        mandatory true;
      }
    }
    output {
      uses npm:package-manifest;
    }
  }

  rpc view {
    description
      "View latest information about a specific package.";
    input {
      leaf name {
        type npm:package-name;
      }
    }
    output {
      uses npm:project;
    }
  }
}
