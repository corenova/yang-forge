module yangforge-controller {
  prefix yfc;

  include yang-v1-extensions;
  import ietf-yang-types { prefix yang; }
  import ietf-yang-library { prefix yanglib; }

  organization
    "ClearPath Networks NFV R&D Group";

  contact
    "Web:  <http://www.clearpathnet.com>
     Code: <http://github.com/clearpath-networks/yangforge>

     Author: Peter K. Lee <mailto:plee@clearpathnet.com>";

  description
    "This module provides YANG v1 language based schema compilations.";

  revision 2015-09-23 {
    description "Enhanced with 0.10.x functionality";
  }
  
  revision 2015-05-04 {
    description "Initial revision";
    reference "RFC-6020";
  }

  feature cli {
    description "When enabled, generates command-line interface";
  }

  feature express {
    description "When enabled, generates HTTP/HTTPS web server instance";
  }
  
  feature restjson {
    description "When enabled, generates REST/JSON web services interface";
    if-feature express;
  }

  feature websocket {
    description "When enabled, generates socket.io websocket interface";
    if-feature express;
  }

  typedef textarea {
    type string {
      length "1..max";
    }
    description
      "The textarea type represents a string that can be multi-line";
  }

  grouping cli-command {
    description
      "The cli-command schema provides general schema format for defining CLI interface RPC input format";
    leaf-list arguments {
      description "The arguments should be 'refined' by uses to override config to true if used";
      type string;
      config false;
    }
    container options {
      description "Placeholder to be 'augmented' during uses to add additional leaf nodes";
    }
  }

  grouping unique-element {
    leaf id { type yang:uuid; }
    leaf name { type string { length 0..100; } }
    leaf description { type string { length 0..2048; } }
    leaf enabled { type boolean; default false; }
  }
  
  container runtime {
    config false;

    uses unique-element;

    leaf owner { type yang:uuid; }
    leaf forgery { type string; }
    list modules {
      description
        "Provides state information about active modules for the current runtime context";
      uses unique-element;
      key "name";
    }
    list features {
      description
        "Provides state information about active features for the current runtime context";
      uses unique-element;
      key "name";
    }
  }

  container registry {
    if-feature registry-service;
    description "Provides module repository service for publish/install";
    list modules {
      key "name";
      uses unique-element;
      leaf data {
        type binary;
        description "Binary type data must be 'explicitly' accessed to retrieve content";
      }
      leaf size { type uint32; units 'Bytes'; mandatory true; }
      leaf checksum { type string; mandatory true; }
    }
  }
  
  // RPC definitions for CLI

  // Common Utilities

  rpc info {
    if-feature cli;
    description "shows info about a specific module";
    input {
      uses cli-command {
        refine arguments {
          config true;
          units "name";
          max-elements 1;
        }
        augment options {
          leaf format {
            description "specify output format (yaml, json)";
            type enumeration {
              enum yaml;
              enum json;
            }
            units f;
            default yaml;
          }
          leaf space {
            description "number of spaces to use for JSON output";
            type uint8 { range 0..8; }
            units s;
            default 2;
          }
          leaf verbose {
            description "increase verbosity";
            type empty;
            units v;
          }
        }
      }
    }
  }

  rpc schema {
    if-feature cli;
    description "process a specific YANG schema file or string";
    input {
      uses cli-command {
        refine arguments {
          config true;
          units "file";
          max-elements 1;
        }
        augment options {
          leaf preprocess {
            description "perform preprocess operation on the input";
            type boolean;
            units p;
          }
          leaf compile {
            description "perform compile operation on the input";
            type boolean;
            units c;
          }
          leaf load {
            description "perform load operation on the input";
            type boolean;
            units l;
          }
          leaf eval {
            description "pass a string from the command line as input";
            type textarea;
            units e;
          }
          leaf format {
            description "specify output format";
            type enumeration {
              enum yaml;
              enum json;
              enum tree;
              enum xml;
            }
            units f;
            default yaml;
          }
          leaf space {
            description "number of spaces to use for JSON output";
            type uint8 { range 0..8; }
            units s;
            default 1;
          }
          leaf output {
            description "set the output filename for compiled schema";
            type string;
            units o;
          }
        }
      }
    }
  }

  rpc translate {
    if-feature cli;
    description "translates input configuration data according to available YANG schema(s)";
    input {
      uses cli-command {
        refine arguments {
          config true;
          units "file";
          max-elements 1;
        }
        augment options {
          leaf format {
            description "specify output format";
            type enumeration {
              enum yaml;
              enum json;
              enum tree;
              enum xml;
            }
            units f;
            default yaml;
          }
          leaf output {
            description "set the output filename";
            type string;
            units o;
          }
        }
      }
    }
  }

  // Lifecycle Utilities
  
  rpc build {
    if-feature cli;
    description "package the application for deployment/publishing";
    input {
      uses cli-command {
        refine arguments {
          config true;
          units "file";
          max-elements 1;
        }
        augment options {
          leaf output {
            description "set the output filename for generated build";
            type string;
            units o;
          }
          leaf gzip {
            description "gzip compress the build output";
            type boolean;
            units z;
          }
        }
      }
    }
  }

  rpc config {
    if-feature cli;
    description "manage yangforge service configuration";
    input {
      uses cli-command {
        // choice argument {
        //   case set {
        //     container argument {
        //       leaf key { type string; mandatory true; }
        //       leaf value { type string; mandatory true; }
        //     }
        //   }
        //   case get {
        //     leaf argument { type string; mandatory true; units key; }
        //   }
        //   case delete {
        //     leaf argument { type string; mandatory true; units key; }
        //   }
        //   case list {
        //     leaf argument { type empty; }
        //   }
        // }
      }
    }
    status planned;
  }
  
  rpc deploy {
    if-feature cli;
    description "deploy application into yangforge endpoint";
    status planned;
  }
  
  rpc publish {
    if-feature cli;
    description "publish package to upstream registry";
    input {
      uses cli-command {
        augment options {
          leaf registry {
            description "The base URL of the package registry";
            type string;
            units r;
            default "http://yangforge.intercloud.net";
          }
        }
      }
    }
    status planned;
  }
  
  rpc run {
    if-feature cli;
    description "runs one or more modules and/or schemas";
    input {
      uses cli-command {
        refine arguments {
          config true;
          units "modules";
        }
        augment options {
          leaf express {
            description "enables express web server on a specified port";
            type union {
              type uint16;
              type binary;
            }
            default 5000;
          }
          leaf restjson {
            description "enables REST/JSON interface";
            type boolean;
            default true;
          }
          leaf websocket {
              description "enables socket.io interface";
              type boolean;
              default true;
          }
        }
      }
    }
  }

  rpc sign {
    if-feature cli;
    description "sign package to ensure authenticity";
    status planned;
  }

  // RPC definitions for server instance

  rpc enable {
    description "enables passed-in set of feature(s) for the current runtime";
    input {
      leaf-list features { type string; }
    }
    output {
      list features { uses unique-element; key "id"; }
    }
  }

  rpc disable {
    description "disables passed-in set of feature(s) for the current runtime";
    input {
      leaf-list features { type string; }
    }
    output {
      list features { uses unique-element; key "id"; }
    }
  }

  rpc infuse {
    if-feature restjson;
    description "absorb requested target module(s) into current runtime";
    input {
      list targets {
        key "source";
        leaf source { type string; mandatory true; }
        container data {
          description "initial configuration data for the source module";
        }
      }
      leaf-list sources { type string; }
    }
    output {
      leaf message { type string; }
      leaf-list modules { type string; }
    }
  }

  rpc defuse {
    if-feature restjson;
    description "discard requested target module(s) from current runtime";
    input {
      leaf-list names { type string; }
    }
    output {
      leaf message { type string; }
    }
  }
}
